Language="VBSCRIPT"

Sub CATMain()

Set documents1 = CATIA.Documents

Set partDocument1 = documents1.Add("Part")

Dim part1 As Part
Set part1 = partDocument1.Part

Dim originElements1 As OriginElements
Set originElements1 = part1.OriginElements

Dim reference1 As Reference
Set reference1 = originElements1.PlaneXY

Dim bodies1 As Bodies
Set bodies1 = part1.Bodies

Dim body1 As Body
Set body1 = bodies1.Item("PartBody")

Dim sketches1 As Sketches
Set sketches1 = body1.Sketches

Dim sketch1 As Sketch
Set sketch1 = sketches1.Add(reference1)

part1.InWorkObject = sketch1

Dim factory2D1 As Factory2D
Set factory2D1 = sketch1.OpenEdition()

Dim piConstant
piConstant = 4 * Atn(1)

Dim diameterMm
diameterMm = 100

Dim radiusMm
radiusMm = diameterMm / 2

Dim verticesX(5)
Dim verticesY(5)
Dim i
For i = 0 To 5
  verticesX(i) = radiusMm * Cos((i * piConstant) / 3)
  verticesY(i) = radiusMm * Sin((i * piConstant) / 3)
Next

For i = 0 To 5
  factory2D1.CreateLine verticesX(i), verticesY(i), verticesX((i + 1) Mod 6), verticesY((i + 1) Mod 6)
Next

sketch1.CloseEdition

part1.Update

End Sub
